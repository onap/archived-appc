/*-
 * ============LICENSE_START=======================================================
 * ONAP : APPC
 * ================================================================================
 * Copyright (C) 2017 AT&T Intellectual Property. All rights reserved.
 * ================================================================================
 * Copyright (C) 2017 Amdocs
 * =============================================================================
 * Licensed under the Apache License, Version 2.0 (the "License");
 * you may not use this file except in compliance with the License.
 * You may obtain a copy of the License at
 * 
 *      http://www.apache.org/licenses/LICENSE-2.0
 * 
 * Unless required by applicable law or agreed to in writing, software
 * distributed under the License is distributed on an "AS IS" BASIS,
 * WITHOUT WARRANTIES OR CONDITIONS OF ANY KIND, either express or implied.
 * See the License for the specific language governing permissions and
 * limitations under the License.
 * 
 * ECOMP is a trademark and service mark of AT&T Intellectual Property.
 * ============LICENSE_END=========================================================
 */

module mdsal-store {
    yang-version 1;

    namespace "org:onap:appc:mdsal:store";
    prefix mdsal-store;

    description
        "Defines api for accepting yang schema as input. Its implementation saves the schema on MD-SAL store";

    revision "2017-09-25" {
        description
                "Initial draft";
    }

    grouping response {
        container status {
            leaf code {
                type uint16;
            }
            leaf message {
                type string;
            }
        }
    }

    rpc store-yang {
        input{
            leaf module-name{
                type string;
            }
            leaf yang{
                type string;
            }
        }
        output{
            uses response;
        }
    }
}
