/*-
 * ============LICENSE_START=======================================================
 * ONAP : APPC
 * ================================================================================
 * Copyright (C) 2017 AT&T Intellectual Property. All rights reserved.
 * ================================================================================
 * Copyright (C) 2017 Amdocs
 * =============================================================================
 * Licensed under the Apache License, Version 2.0 (the "License");
 * you may not use this file except in compliance with the License.
 * You may obtain a copy of the License at
 * 
 *      http://www.apache.org/licenses/LICENSE-2.0
 * 
 * Unless required by applicable law or agreed to in writing, software
 * distributed under the License is distributed on an "AS IS" BASIS,
 * WITHOUT WARRANTIES OR CONDITIONS OF ANY KIND, either express or implied.
 * See the License for the specific language governing permissions and
 * limitations under the License.
 * 
 * ECOMP is a trademark and service mark of AT&T Intellectual Property.
 * ============LICENSE_END=========================================================
 */

module mdsal-store-impl {

    yang-version 1;
    namespace "org:onap:appc:mdsal:store:impl";
    prefix mdsal-store-impl;

    import config { prefix config; revision-date 2013-04-05; }
    import opendaylight-md-sal-binding { prefix mdsal; revision-date 2013-10-28; }

     description
        "This module contains the base YANG definitions for
         mdsal-store-impl implementation.";

    revision "2017-09-25" {
        description
            "Initial revision.";
    }

    // This is the definition of the service implementation as a module identity.
    identity mdsal-store-impl {
            base config:module-type;

            // Specifies the prefix for generated java classes.
            config:java-name-prefix MdsalStoreProvider;
    }

    // Augments the 'configuration' choice node under modules/module.
    // We consume the two main services, RPCs and DataStore
    // Notification service is not used
    augment "/config:modules/config:module/config:configuration" {
        case mdsal-store-impl {
            when "/config:modules/config:module/config:type = 'mdsal-store-impl'";

            container rpc-registry {
                uses config:service-ref {
                    refine type {
                        mandatory true;
                        config:required-identity mdsal:binding-rpc-registry;
                    }
                }
            }

            container notification-service {
                uses config:service-ref {
                    refine type {
                        mandatory true;
                        config:required-identity mdsal:binding-notification-service;
                    }
                }
            }

            container data-broker {
                uses config:service-ref {
                    refine type {
                        mandatory false;
                        config:required-identity mdsal:binding-async-data-broker;
                    }
                }
            }
        }
    }
}
